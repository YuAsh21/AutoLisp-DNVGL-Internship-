(defun c:test (/ pnt cent txt)
  (while (setq pnt (getpoint "\nSpecify center point for circle <exit>: "))
    (command-s "_.CIRCLE" "_none" pnt)
    (if (setq pnt (getpoint "\nSpecify text:"))
    (command "_Text" "_j" "_m" pnt "" "" txt)
    (princ)
    (if (setq pnt (getpoint "\nSpecify first point for line <no line>: "))
      (command "_.LINE" "_none" pnt PAUSE "")))
  (princ)
)
