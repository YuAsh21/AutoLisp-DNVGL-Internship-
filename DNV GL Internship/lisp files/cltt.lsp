(defun c:CLTT (/ pnt txt ent)
  (while (setq pnt (getpoint "\nSpecify center point for circle <exit>: "))
    (command-s "_.CIRCLE" "_none" pnt)
    (command ".dtext" "j" "mc" pause "" "")
  (princ)
    (if (setq pnt (getpoint "\nSpecify first point for line <no line>: "))
      (command "_.LINE" "_none" pnt PAUSE "")))
  (princ)
)
